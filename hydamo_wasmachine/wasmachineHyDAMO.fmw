FME workspace wasmachineHyDAMO.fmw

Parameters:
- DestDataset_OGCGEOPACKAGE =
- FEATURE_TYPES =
- FEATURE_TYPES_2 =
- PARAMETER_Waterbeheerder =
- SourceDataset_FILEGDB =
- SourceDataset_OGCGEOPACKAGE_5 =
- SourceDataset_XLSXR =

Readers:
- XLSXR_1: XLSXR from $(SourceDataset_XLSXR)
- XLSXR_2: XLSXR from $(SourceDataset_XLSXR)
- OGCGEOPACKAGE_1: OGCGEOPACKAGE from $(SourceDataset_OGCGEOPACKAGE_5)
- FILEGDB_1: FILEGDB from $(SourceDataset_FILEGDB)

Writers:
- OGCGEOPACKAGE_2: OGCGEOPACKAGE to $(DestDataset_OGCGEOPACKAGE)
- OGCGEOPACKAGE_3: OGCGEOPACKAGE to $(DestDataset_OGCGEOPACKAGE)

Kolommen (reader XLSXR_2)
    attributes: ConnectVersie number(3,1), Opmerking string, BronKolomVersie number(3,1), BronTabel char(31), BronTabelAlias char(2), BronKolom char(31), BronKolomType char(16), BronKolomLengte char(12), BronKolomDecimalen number(2,0), BronKolomDomein char(39), BronKolomConditie string, DoelTabel char(27), DoelKolom char(31), DoelKolomType char(16), DoelKolomLengte number(5,0), DoelKolomDecimalen number(2,0), DoelKolomDomein char(39), DoelKolomDefault string, BronTabelMaster string, BronKolomMaster char(9), DoelTabelMaster char(27), DoelKolomMaster char(9), ObjectGuidDoel char(39), AttributeGuidDoel char(39), KeywordsBron char(18), KeywordsDoel char(18)
    -> Tester_4
Tester_4
    BOOL_OP = OR
    COMPOSITE_TEST = 1
    TEST_CLAUSE = TEST @Value(DoelKolomType) IN Point,Polygon,Polyline
    TEST_MODE = TEST
    FAILED -> AttributeFilter_2
AttributeFilter_2
    ATTR_NAME = DoelKolom
    ATTR_VALUES = <Empty>,<Missing>,<Null>,<Unfiltered>
    <UNFILTERED> -> AttributeManager_2
Note: Bronvelden selecteren en hernoemen
AttributeManager_2
    ATTR_TABLE:
      REMOVE versieBron
      RENAME_SET_VALUE DoelTabel > tabelnaam
      RENAME_SET_VALUE DoelKolom > veldnaam
      RENAME_SET_VALUE DoelKolomType > veldtype = FME_CONDITIONAL:DEFAULT_VALUE'_FME_NO_OP_'BOOL_OP;OR;COMPOSITE_TEST;1;TEST DoelKolomDomein ATTRIBUTE_HAS_A_VALUE _FME_BLANK_STRING_'fme_buffer'BOOL_OP;OR;COMPOSITE_TEST;1;TEST @Value(veldtype) = CharacterString'fme_buffer'BOOL_OP;OR;COMPOSITE_TEST;1;TEST @Value(veldtype) = Integer'fme_int32'BOOL_OP;OR;COMPOSITE_TEST;1;TEST @Value(veldtype) = Date'fme_datetime'BOOL_OP;OR;COMPOSITE_TEST;1;TEST @Value(veldtype) = Decimal'fme_real64'BOOL_OP;OR;COMPOSITE_TEST;1;TEST @Value(veldtype) = Real'fme_real64'FME_NUM_CONDITIONS7___
    -> DuplicateFilter_4
    -> Tester_3
Note: veldnaam shape verwijderen
Tester_3
    BOOL_OP = OR
    COMPOSITE_TEST = 1
    TEST_CLAUSE = TEST @Value(veldnaam) NOT_= shape
    TEST_MODE = TEST
    PASSED -> AttributeManager
Note: Bepalen feature_type
DuplicateFilter_4
    INPUT_ORDERED_CHOICE = No
    KEYATTR = tabelnaam
    UNIQUE -> FeatureMerger [REQUESTOR]
Note: HyDAMO File Geodatabase
AfvoergebiedAanvoergebied (reader FILEGDB_1)
    attributes: OBJECTID objectid, code text(50), globalID globalid, naam text(100), statusObject text(18), hyperlink text(256), opmerking text(2000), namespace text(50), detailNiveauGeometrie int, LVpublicatiedatum date, soortAfvoerAanvoergebied text(18), ordeCode text(100), ordeScope text(52), ordeSystematiek text(36), gerelateerdAfAanvoergebied int, ontstaanswijze text(20), waterafvoer int, oppervlakte double, metadataID guid, lateraleKnoopID guid, se_anno_cad_data blob, Shape_Length double, Shape_Area double, DAMODomeinID guid, DAMODomeinNaam text(100), DAMOKolomID guid, DAMOKolomNaam text(100), DAMONaam text(50), DAMOTabelID guid, DAMOTabelNaam text(100),
      ProfielPuntID guid, aantalDoorstroomopeningen int, actiewaarde double, afslagpeil double, afstand double, afvoerCoefficient double, afvoercoefficient double, aquaductID guid, beginPeriode text(50), bergingsgebiedID guid, bevat int, bochtEnKnikverlies double, bodemWeerstand double, bodemhoogteBenedenstrooms double, bodemhoogteBovenstrooms double, bodemvalID guid, bovengrens double, breedte double, breedteOpening double, bronDefinitie text(256), bronDefinitieLink text(256), bronVulWaarde text(256), brugID guid, categorie text(54), categorieOppwaterlichaam text(9), codeVolgnummer int, conditie text(1000), datumInwinning date, debiet double, definitie text(1000),
      dimensie text(2), doelvariabele text(12), doorstroombreedte double, doorstroomlengte double, doorvaartBreedte double, draineert int, drempelpeil double, duikersifonhevelID guid, eenheid text(256), eenheidActiewaarde text(9), eenheidDoelvariabele text(9), eenheidMeetwaarde text(9), eindPeriode text(50), fieldLength text(50), fieldType text(50), filterUitstroming text(3), flux double, functieGemaal text(24), gemaalID guid, getijdeBeinvloed text(3), grondwaterKoppelLijnID guid, grondwaterKoppelPuntID guid, grondwaterkoppellijnID guid, hoogsteDoorstroombreedte double, hoogsteDoorstroomhoogte double, hoogte double, hoogteBinnenOnderkantBene double, hoogteBinnenOnderkantBov double, hoogteBovenzijde double, hoogteConstructie double,
      hoogteOnderzijde double, hoogteOpening double, hydroObjectGroeperingID guid, hydroObjectID guid, hydrologischerandvoorwaardeID guid, hydroobjectID guid, indPeilRegulPeilScheidend text(8), indicatieComplexeSturing text(19), indicatieWaterkerend text(19), infiltratiefactor double, intreeverlies double, inwinnendeInstantie text(52), inwinningsMethode text(16), kerendeHoogte double, kruinbreedte double, krwStromendID guid, kunstwerkopeningID guid, laagsteDoorstroombreedte double, laagsteDoorstroomhoogte double, lengte double, maximaleCapaciteit double, maximaleHoogteBovenkant double, meetlocatieID guid, meetwaarde double, metendeInstantie text(100), metingOmschrijving text(250), minimaleCapaciteit double, minimaleHoogteBovenkant double, naamspace text(50), natteOmtrek double,
      nauwkeurigheidXY smallint, nauwkeurigheidZ smallint, niveau text(20), normgeparamprofielID guid, ondergrens double, ontwerpBuitenWaterstand double, openingspeil double, openkeerpeil double, oppervlaktewaterlichaamID guid, oppwaterVolgnummer int, opstellingPomp text(23), overlaatOnderlaat text(9), peilafwijkingGebiedID guid, peilgebiedPraktijkID guid, peilgebiedVigerendID guid, persistentie text(11), pompID guid, pompcurve text(256), pomprichting text(8), prioriteit text(6), profielgroepID guid, profiellijnID guid, profielweergave text(26), referentievlak text(15), regelmiddelID guid, regenwaterbufferCompartimentID guid, richting single, rioolgemaalID guid, ruimtelijkeAfbakeningBekend text(3), ruwheid double,
      ruwheidHoog double, ruwheidLaag double, signaleringspeil double, sluitpeil double, soortAandrijving text(19), soortMateriaal text(19), soortMeetpunt text(47), soortOppwaterkwaliteit text(49), soortOppwaterkwantiteit text(36), soortOverspanning text(61), soortParameter text(34), soortProfiel text(36), soortRegelbaarheid text(27), soortRegelmiddel text(18), soortStreefpeil text(27), soortStuw text(24), status text(18), statusLeggerWatersysteem text(19), statusLeggerWaterveiligheid text(19), statusPeilgebied text(19), streefwaarde double, sturingID guid, stuurvariabele text(28), stuwID guid, tekencode text(60), tijd date, typeController text(9), typeHydraulischObject text(10), typeKruising text(8), typeMateriaaRegelmiddel text(19),
      typePomp text(14), typePompschakeling text(9), typeRandvoorwaarde text(26), typeRuwheid text(15), typeSturing text(8), typeWaterkerendeConstructie text(58), uittreeverlies double, uniek text(50), vaarwegID guid, vasteWaarde double, voertAfOp int, vormKoker text(15), vormOpening text(15), vulWaarde text(100), waarde double, waterhoogte double, waterkeringID guid, waterstand double
    -> StringCaseChanger
Note: HyDAMO Geopackage
AfvoergebiedAanvoergebied (reader OGCGEOPACKAGE_1)
    attributes: code text(200), globalID text(50), naam text(200), statusObject int, CREATED_DATE datetime, LAST_EDITED_DATE datetime, hyperlink text(500), administratiefgebied int, soortAfvoerAanvoergebied int, ordeCode text(200), oppervlakte double, lateraleknoopID text(200), afvoerCoefficient double, bochtEnKnikverlies double, breedte double, breedteOpening double, categorieOppwaterlichaam int, doorstroomlengte double, duikersifonhevelID text(200), gemaalID text(200), hoogsteDoorstroombreedte double, hoogsteDoorstroomhoogte double, hoogte double, hoogteBinnenOnderkantBene double, hoogteBinnenOnderkantBov double, hoogteBovenzijde double, hoogteConstructie double, hoogteOnderzijde double, hoogteOpening double, indPeilRegulPeilScheidend int,
      intreeverlies double, kruinbreedte double, kunstwerkopeningID text(200), laagsteDoorstroombreedte double, laagsteDoorstroomhoogte double, lengte double, maximaleCapaciteit double, maximaleHoogteBovenkant double, minimaleHoogteBovenkant double, overlaatOnderlaat int, pompcurve text(200), pomprichting int, richting double, ruwheid double, ruwheidHoog double, ruwheidLaag double, soortRegelbaarheid int, soortRegelmiddel int, soortStuw int, stuwID text(200), typeKruising int, typeRuwheid int, uittreeverlies double, vormKoker int, vormOpening int
    -> StringCaseChanger
StringCaseChanger
    ATTRCHOICE = Selected Attributes
    ATTRLIST = fme_feature_type
    CHANGE_TYPE = Title case
    -> Tester_5
Note: Test of ObjectiD aanwezig is
Tester_5
    BOOL_OP = OR
    COMPOSITE_TEST = 1
    TEST_CLAUSE = TEST OBJECTID ATTRIBUTE_IS_MISSING ""
    TEST_MODE = TEST
    PASSED -> AttributeManager_4
    FAILED -> AttributeManager_5
AttributeManager_5
    ATTR_TABLE = SET_TO globalID = FME_CONDITIONAL:DEFAULT_VALUE'{@UUID()}'BOOL_OP;OR;COMPOSITE_TEST;1;TEST globalID ATTRIBUTE_HAS_A_VALUE _FME_BLANK_STRING_'@Value(globalID)'FME_NUM_CONDITIONS2___
    -> BulkAttributeRenamer
AttributeManager_4
    ATTR_TABLE:
      SET_TO globalID = FME_CONDITIONAL:DEFAULT_VALUE'{@UUID()}'BOOL_OP;OR;COMPOSITE_TEST;1;TEST globalID ATTRIBUTE_HAS_A_VALUE _FME_BLANK_STRING_'@Value(globalID)'FME_NUM_CONDITIONS2___
      SET_TO objectID = @Evaluate(@Count(object,1))
    -> BulkAttributeRenamer
BulkAttributeRenamer
    ATTRCHOICE = All Attributes
    CASE_CHANGE_TYPE = lower
    MODE_CHOICE = RENAME
    PATTERN_ACTION_DISP = CASECHANGE
    -> FeatureJoiner_3 [RIGHT]
    -> AttributeExploder
AttributeExploder
    ATTR_NAME_LABEL = _attr_name
    ATTR_VALUE_LABEL = _attr_value
    EXPLODING_TYPE = Features
    KEEP_ATTRIBUTES = Yes
    KEEP_GEOMETRY = No
    -> AttributeKeeper
AttributeKeeper
    CREATE_BULK_MODE_FEATURES = NO
    KEEP_ATTRS = fme_feature_type,_attr_name,_attr_value,globalid
    -> FeatureJoiner_2 [LEFT]
Kolommen (reader XLSXR_1)
    attributes: ConnectVersie number(3,1), Opmerking string, BronKolomVersie number(3,1), BronTabel char(31), BronTabelAlias char(2), BronKolom char(31), BronKolomType char(16), BronKolomLengte char(12), BronKolomDecimalen number(2,0), BronKolomDomein char(39), BronKolomConditie string, DoelTabel char(27), DoelKolom char(31), DoelKolomType char(16), DoelKolomLengte number(5,0), DoelKolomDecimalen number(2,0), DoelKolomDomein char(39), DoelKolomDefault string, BronTabelMaster string, BronKolomMaster char(9), DoelTabelMaster char(27), DoelKolomMaster char(9), ObjectGuidDoel char(39), AttributeGuidDoel char(39), KeywordsBron char(18), KeywordsDoel char(18)
    -> AttributeFilter
AttributeFilter
    ATTR_NAME = DoelKolomDomein
    ATTR_VALUES = <Empty>,<Missing>,<Null>,<Unfiltered>
    <UNFILTERED> -> FeatureJoiner [LEFT]
DomeinenWaarden (reader XLSXR_1)
    attributes: ConnectVersie number(3,1), BronDomeinVersie number(3,1), BronDomein char(45), BronDomeinWaarde char(18), BronDomeinOmschrijving char(80), DoelDomein char(45), DoelDomeinWaarde char(18), DoelDomeinOmschrijving char(80), DomainValueguidDoel char(39), AliasBron char(16), AliasDoel char(16)
    -> FeatureJoiner [RIGHT]
FeatureJoiner
    ATTR_CONFLICT_RES = Use Left
    GEOMETRY_HANDLING = Use Left
    JOIN_KEYS = DoelKolomDomein DoelDomein AUTO
    JOIN_MODE = Inner
    JOINED -> FeatureJoiner_2 [RIGHT]
FeatureJoiner_2
    ATTR_CONFLICT_RES = Use Left
    GEOMETRY_HANDLING = Use Left
    JOIN_KEYS = fme_feature_type DoelTabel AUTO _attr_name DoelKolom AUTO _attr_value DoelDomeinWaarde AUTO
    JOIN_MODE = Inner
    JOINED -> AttributeCreator
    <REJECTED> -> FeatureJoiner_2__Rejected_
Note: Attributen maken voor alle kolommen die in een domein zitten (o.b.v. de waarde van DoelKolom)
AttributeCreator
    ATTR_TABLE = SET_TO @Value(DoelKolom) = @Value(DoelDomeinOmschrijving)
    -> AttributeRemover
Note: Alle Doel... kolommen en _attr_name en _attr_value verwijderen
AttributeRemover
    REMOVE_ATTRS = _attr_name,_attr_value,DoelTabel,DoelDomein,DoelDomeinOmschrijving,DoelDomeinWaarde,DoelKolom,DoelKolomDomein
    -> Aggregator_2
Note: Aggregeren op fme_feature_type en globalid
Aggregator_2
    ACCUM_ATTRS_NAME = Merge Incoming Attributes
    AGGREGATE_TYPE = Homogeneous Collection (If Possible)
    GROUP_BY = fme_feature_type globalid
    MODE = Geometry - Assemble One Level
    SEP = ,
    AGGREGATE -> FeatureJoiner_3 [LEFT]
Note: Bevat dus voor elk feature ALLE kolommen die in een domein zitten. Bij wegschrijven dus alleen de kolommen pakken die van toepassing zijn
FeatureJoiner_3
    ATTR_CONFLICT_RES = Use Left
    GEOMETRY_HANDLING = Use Right
    JOIN_KEYS = fme_feature_type fme_feature_type AUTO globalid globalid AUTO
    JOIN_MODE = Inner
    JOINED -> FeatureMerger_2 [REQUESTOR]
    UNJOINED_RIGHT -> FeatureMerger_2 [REQUESTOR]
    <REJECTED> -> Tester_2
Tester_2
    BOOL_OP = OR
    COMPOSITE_TEST = 1
    TEST_CLAUSE = TEST @Value(fme_rejection_code) = MISSING_RIGHT_KEY
    TEST_MODE = TEST
    PASSED -> FeatureMerger_2 [REQUESTOR]
FeatureJoiner_2__Rejected_: Inspector [off]
Note: Voor fme Schema Feature en aggregator op basis van Subgroep / name-> nen3610id / fme_data_type-> fme_buffer
Creator
    GEOMTYPE = Geometry Object
    NUM = 1
    CREATED -> FeatureMerger [SUPPLIER]
FeatureMerger
    ATTR_ACCUM_MODE = Merge Supplier
    ATTR_CONFLICT_RES = Use Supplier
    IGNORE_NULLS = No
    JOIN_KEYS = 1 1 AUTO
    MERGE_TYPE = Attributes Only
    PROCESS_DUPS = NO
    REJECT_NULL_MISSING_KEYS = No
    SUPPLIERS_FIRST = No
    MERGED -> AttributeManager
Note: Input Attribute / Output Attribute / tabelnaam / fme_feature_type / veldnaam / name / veldtype / fme_data_type
AttributeManager
    ATTR_TABLE:
      RENAME_SET_VALUE tabelnaam > fme_feature_type
      RENAME_SET_VALUE veldnaam > name
      RENAME_SET_VALUE veldtype > fme_data_type
      REMOVE _creation_instance
      REMOVE fme_geometry
      REMOVE fme_type
      REMOVE DoelKolomLengte
      REMOVE DoelKolomDomein
    -> ListBuilder
ListBuilder
    GROUP_BY = fme_feature_type
    LIST_ATTRS_TO_INCLUDE = fme_data_type name
    LIST_NAME = attribute
    -> Junction
Junction
    -> FeatureMerger_2 [SUPPLIER]
FeatureMerger_2
    ATTR_ACCUM_MODE = Merge Supplier
    ATTR_CONFLICT_RES = Use Requestor
    IGNORE_NULLS = No
    JOIN_KEYS = @Value(fme_feature_type) @Value(fme_feature_type) AUTO
    MERGE_TYPE = Attributes Only
    PROCESS_DUPS = NO
    REJECT_NULL_MISSING_KEYS = No
    SUPPLIERS_FIRST = No
    MERGED -> AttributeManager_3
AttributeManager_3
    ATTR_TABLE = SET_TO nen3610id = NL.WBHCODE.$(PARAMETER_Waterbeheerder).@Value(fme_feature_type).@Value(objectid)
    -> Tester
Tester
    BOOL_OP = OR
    COMPOSITE_TEST = 1
    TEST_CLAUSE = TEST @Value(fme_geometry) != fme_undefined
    TEST_MODE = TEST
    PASSED -> Table1 (writer OGCGEOPACKAGE_2)
    FAILED -> Table1 (writer OGCGEOPACKAGE_3)
Table1 (writer OGCGEOPACKAGE_2)
Table1 (writer OGCGEOPACKAGE_3)
